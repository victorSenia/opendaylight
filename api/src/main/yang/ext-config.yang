module ext-config {
    yang-version 1;
		namespace "urn:opendaylight:params:xml:ns:yang:ext:config";
    prefix "ext-config";

    import config {prefix config; revision-date 2013-04-05;}

    description
        "Extensions in openflow library.";

    revision "2016-11-01" {
        description "Initial revision";
    }

		identity openflowjava-extension {
        base config:module-type;
        config:java-name-prefix ExtensionProvider;
    }

		augment "/config:modules/config:module/config:configuration" {
        case openflowjava-extension {
            when "/config:modules/config:module/config:type = 'openflowjava-extension'";

            list openflow-switch-connection-provider {
                uses config:service-ref {
                    refine type {
                        mandatory true;
                        config:required-identity openflow-switch-connection-provider:openflow-switch-connection-provider;
                    }
                }
            }
        }
    }
}
